XMS3500-MIB DEFINITIONS ::= BEGIN

     --  The XMS3500 branch represents the 3G part of the XMS MIB
     --  A 2G (or legacy) branch is still available under the OID tbsProxyDbs2930 (1.3.6.1.4.1.2258.2).

     IMPORTS
          MODULE-IDENTITY, OBJECT-TYPE, NOTIFICATION-TYPE, enterprises,
          Integer32, Counter32, TimeTicks, Unsigned32
               FROM SNMPv2-SMI
          DisplayString, PhysAddress, DateAndTime, RowStatus
               FROM SNMPv2-TC
          MODULE-COMPLIANCE, OBJECT-GROUP
               FROM SNMPv2-CONF;


     Boolean ::= TEXTUAL-CONVENTION
          STATUS       current
          DESCRIPTION  "Represents a boolean value."
          SYNTAX       INTEGER { false(2), true(1) }


     OBJECTID ::= TEXTUAL-CONVENTION
          STATUS       current
          DESCRIPTION  "Represents a OID value."
          SYNTAX       OBJECT IDENTIFIER


     --  The very top of XMS3500 branch

     gvg OBJECT IDENTIFIER ::= { enterprises 4947 }

     gvgRegistrations OBJECT IDENTIFIER ::= { gvg 2 }

     gvgManagementSystem OBJECT IDENTIFIER ::= { gvgRegistrations 14 }


     --  MODULE-IDENTITY

     xms3500 MODULE-IDENTITY

          LAST-UPDATED  "1211171130Z"
          ORGANIZATION  "THOMSON"
          CONTACT-INFO  "http://www.thomson-networks.com/contact-us/technical-support/"
          DESCRIPTION   "The XMS3500 MIB"

          REVISION      "1211171130Z"
          DESCRIPTION   "Automatic generation with : asn1.awk V1.10"

          REVISION      "1211171130Z"
          DESCRIPTION   "Version Tag < Service>"

          ::= { gvgManagementSystem 1 }


     --------------------------
     --  OBJECTS DEFINITION
     --------------------------

     --------------------------
     --  Objects under general branch
     --------------------------

     general OBJECT IDENTIFIER ::= { xms3500 1 }


     -------
     -- genManagerTable definition
     -------

     genManagerTable OBJECT-TYPE
          SYNTAX       SEQUENCE OF GenManagerEntry
          MAX-ACCESS   not-accessible
          STATUS       current
          DESCRIPTION  ""
          ::= { general 1 }

     genManagerEntry OBJECT-TYPE
          SYNTAX       GenManagerEntry
          MAX-ACCESS   not-accessible
          STATUS       current
          DESCRIPTION  ""
          INDEX        { genManagerIpAddress, genManagerPort }
          ::= { genManagerTable 1 }

     GenManagerEntry ::=
          SEQUENCE {
                     genManagerIpAddress
                          IpAddress,
                     genManagerPort
                          INTEGER,
                     genManagerTrapEnable
                          Boolean,
                     genManagerTrapTypeSelection
                          INTEGER,
                     genManagerEventTrapSeverityFilter
                          INTEGER,
                     genManagerRowStatus
                          RowStatus
                   }

     genManagerIpAddress OBJECT-TYPE
          SYNTAX       IpAddress 
          MAX-ACCESS   read-write
          STATUS       current
          DESCRIPTION  "The manager IP address"
          ::= { genManagerEntry 1 }

     genManagerPort OBJECT-TYPE
          SYNTAX       INTEGER 
          MAX-ACCESS   read-write
          STATUS       current
          DESCRIPTION  "The manager port"
          ::= { genManagerEntry 2 }

     genManagerTrapEnable OBJECT-TYPE
          SYNTAX       Boolean 
          MAX-ACCESS   read-write
          STATUS       current
          DESCRIPTION  "Enable or not sending traps of any type towards this manager"
          ::= { genManagerEntry 3 }

     genManagerTrapTypeSelection OBJECT-TYPE
          SYNTAX       INTEGER 
          MAX-ACCESS   read-write
          STATUS       current
          DESCRIPTION  "Specify the types of trap to be sent (1 bit per type, value 0 = disabled). bit0 : genTrapAlarm, bit1: genTrapTopology, bit2: genTrapConfigXxx, bit3: genTrapRedundancy, bit4 : genTrapEvent"
          ::= { genManagerEntry 4 }

     genManagerEventTrapSeverityFilter OBJECT-TYPE
          SYNTAX       INTEGER {
                                 allSeverity(2),
                                 severityWarning(3),
                                 severityMinor(4),
                                 severityMajor(5),
                                 severityCritical(6)
                               }
          MAX-ACCESS   read-write
          STATUS       current
          DESCRIPTION  "Only event traps whose severity is higher or equal this value will be sent, and associated events of severity cleared"
          ::= { genManagerEntry 5 }

     genManagerRowStatus OBJECT-TYPE
          SYNTAX       RowStatus 
          MAX-ACCESS   read-create
          STATUS       current
          DESCRIPTION  "Status of row"
          ::= { genManagerEntry 6 }


     -------
     -- genAlarmTable definition
     -------

     genAlarmTable OBJECT-TYPE
          SYNTAX       SEQUENCE OF GenAlarmEntry
          MAX-ACCESS   not-accessible
          STATUS       current
          DESCRIPTION  ""
          ::= { general 3 }

     genAlarmEntry OBJECT-TYPE
          SYNTAX       GenAlarmEntry
          MAX-ACCESS   not-accessible
          STATUS       current
          DESCRIPTION  ""
          INDEX        { genAlarmOrigin, genAlarmIndex }
          ::= { genAlarmTable 1 }

     GenAlarmEntry ::=
          SEQUENCE {
                     genAlarmIndex
                          INTEGER,
                     genAlarmOrigin
                          DisplayString,
                     genAlarmResourceId
                          DisplayString,
                     genAlarmProbableCause
                          Unsigned32,
                     genAlarmSpecificProblem
                          DisplayString,
                     genAlarmTime
                          DateAndTime,
                     genAlarmSeverity
                          INTEGER,
                     genAlarmCategory
                          INTEGER,
                     genAlarmLabel
                          DisplayString
                   }

     genAlarmIndex OBJECT-TYPE
          SYNTAX       INTEGER 
          MAX-ACCESS   read-only
          STATUS       current
          DESCRIPTION  "Index in the table"
          ::= { genAlarmEntry 1 }

     genAlarmOrigin OBJECT-TYPE
          SYNTAX       DisplayString 
          MAX-ACCESS   read-only
          STATUS       current
          DESCRIPTION  "Identification of the origin of the alarm"
          ::= { genAlarmEntry 2 }

     genAlarmResourceId OBJECT-TYPE
          SYNTAX       DisplayString 
          MAX-ACCESS   read-only
          STATUS       current
          DESCRIPTION  "Identification of the resource or interface that raises the alarm"
          ::= { genAlarmEntry 3 }

     genAlarmProbableCause OBJECT-TYPE
          SYNTAX       Unsigned32 
          MAX-ACCESS   read-only
          STATUS       current
          DESCRIPTION  "Enumerated value identifying the cause of the alarm"
          ::= { genAlarmEntry 4 }

     genAlarmSpecificProblem OBJECT-TYPE
          SYNTAX       DisplayString 
          MAX-ACCESS   read-only
          STATUS       current
          DESCRIPTION  "Additional information that provide furthers explanations for the probable cause"
          ::= { genAlarmEntry 5 }

     genAlarmTime OBJECT-TYPE
          SYNTAX       DateAndTime 
          MAX-ACCESS   read-only
          STATUS       current
          DESCRIPTION  "UTC date and time of the alarm raising"
          ::= { genAlarmEntry 6 }

     genAlarmSeverity OBJECT-TYPE
          SYNTAX       INTEGER {
                                 severityIndeterminate(2),
                                 severityWarning(3),
                                 severityMinor(4),
                                 severityMajor(5),
                                 severityCritical(6)
                               }
          MAX-ACCESS   read-only
          STATUS       current
          DESCRIPTION  "X733 alarm severity"
          ::= { genAlarmEntry 7 }

     genAlarmCategory OBJECT-TYPE
          SYNTAX       INTEGER {
                                 communication(1),
                                 qualityOfService(2),
                                 processing(3),
                                 equipment(4),
                                 environment(5),
                                 other(6)
                               }
          MAX-ACCESS   read-only
          STATUS       current
          DESCRIPTION  "X733 alarm category"
          ::= { genAlarmEntry 8 }

     genAlarmLabel OBJECT-TYPE
          SYNTAX       DisplayString 
          MAX-ACCESS   read-only
          STATUS       current
          DESCRIPTION  "Clear description of the alarm"
          ::= { genAlarmEntry 9 }


     -------
     -- genEventTable definition
     -------

     genEventTable OBJECT-TYPE
          SYNTAX       SEQUENCE OF GenEventEntry
          MAX-ACCESS   not-accessible
          STATUS       current
          DESCRIPTION  ""
          ::= { general 4 }

     genEventEntry OBJECT-TYPE
          SYNTAX       GenEventEntry
          MAX-ACCESS   not-accessible
          STATUS       current
          DESCRIPTION  ""
          INDEX        { genEventRecordId }
          ::= { genEventTable 1 }

     GenEventEntry ::=
          SEQUENCE {
                     genEventRecordId
                          Unsigned32,
                     genEventType
                          INTEGER,
                     genEventTime
                          DateAndTime,
                     genEventOrigin
                          DisplayString,
                     genEventResourceId
                          DisplayString,
                     genEventProbableCause
                          Unsigned32,
                     genEventSpecificProblem
                          DisplayString,
                     genEventSeverity
                          INTEGER,
                     genEventCategory
                          INTEGER,
                     genEventLabel
                          DisplayString
                   }

     genEventRecordId OBJECT-TYPE
          SYNTAX       Unsigned32 
          MAX-ACCESS   read-only
          STATUS       current
          DESCRIPTION  "Unique identifier of the event (internal counter)"
          ::= { genEventEntry 1 }

     genEventType OBJECT-TYPE
          SYNTAX       INTEGER {
                                 typeObjectCreation(1),
                                 typeObjectDeletion(2),
                                 typeObjectChange(3),
                                 typeAttributeValueChange(4),
                                 typeAlarm(5),
                                 typeActionPerformed(6),
                                 typeErrorInformation(7)
                               }
          MAX-ACCESS   read-only
          STATUS       current
          DESCRIPTION  "X733 event type"
          ::= { genEventEntry 2 }

     genEventTime OBJECT-TYPE
          SYNTAX       DateAndTime 
          MAX-ACCESS   read-only
          STATUS       current
          DESCRIPTION  "UTC date and time of the event raising"
          ::= { genEventEntry 3 }

     genEventOrigin OBJECT-TYPE
          SYNTAX       DisplayString 
          MAX-ACCESS   read-only
          STATUS       current
          DESCRIPTION  "Identification of the origin of the alarm"
          ::= { genEventEntry 4 }

     genEventResourceId OBJECT-TYPE
          SYNTAX       DisplayString 
          MAX-ACCESS   read-only
          STATUS       current
          DESCRIPTION  "Identification of the resource or interface that raises the event"
          ::= { genEventEntry 5 }

     genEventProbableCause OBJECT-TYPE
          SYNTAX       Unsigned32 
          MAX-ACCESS   read-only
          STATUS       current
          DESCRIPTION  "Significant for alarm : Enumerated value identifying the cause of the alarm"
          ::= { genEventEntry 6 }

     genEventSpecificProblem OBJECT-TYPE
          SYNTAX       DisplayString 
          MAX-ACCESS   read-only
          STATUS       current
          DESCRIPTION  "Significant for alarm : Additional information that provide furthers explanations for the probable cause"
          ::= { genEventEntry 7 }

     genEventSeverity OBJECT-TYPE
          SYNTAX       INTEGER {
                                 severityCleared(1),
                                 severityIndeterminate(2),
                                 severityWarning(3),
                                 severityMinor(4),
                                 severityMajor(5),
                                 severityCritical(6)
                               }
          MAX-ACCESS   read-only
          STATUS       current
          DESCRIPTION  "Significant for alarm : X733 alarm severity"
          ::= { genEventEntry 8 }

     genEventCategory OBJECT-TYPE
          SYNTAX       INTEGER {
                                 communication(1),
                                 qualityOfService(2),
                                 processing(3),
                                 equipment(4),
                                 environment(5),
                                 other(6)
                               }
          MAX-ACCESS   read-only
          STATUS       current
          DESCRIPTION  "Significant for alarm : X733 alarm category"
          ::= { genEventEntry 9 }

     genEventLabel OBJECT-TYPE
          SYNTAX       DisplayString 
          MAX-ACCESS   read-only
          STATUS       current
          DESCRIPTION  "Clear description of the event"
          ::= { genEventEntry 10 }


     --------------------------
     --  Objects under genSystem branch
     --------------------------

     genSystem OBJECT IDENTIFIER ::= { general 5 }

     genSoftwareVersion OBJECT-TYPE
          SYNTAX       DisplayString (SIZE(0..80))
          MAX-ACCESS   read-only
          STATUS       current
          DESCRIPTION  "XMS version"
          ::= { genSystem 1 }


     --------------------------
     --  Objects under genTraps branch
     --------------------------

     genTraps OBJECT IDENTIFIER ::= { general 7 }


     --------------------------
     --  Objects under genTrapSpecificVariables branch
     --------------------------

     genTrapSpecificVariables OBJECT IDENTIFIER ::= { genTraps 1 }

     genTrapLastNumber OBJECT-TYPE
          SYNTAX       Unsigned32 
          MAX-ACCESS   accessible-for-notify
          STATUS       current
          DESCRIPTION  "Sequence number of the last trap sent, unique trap counter for all registered managers."
          ::= { genTrapSpecificVariables 1 }

     genTrapPreviousNumber OBJECT-TYPE
          SYNTAX       Unsigned32 
          MAX-ACCESS   accessible-for-notify
          STATUS       current
          DESCRIPTION  "Sequence number of the previous trap sent to the same manager. This variable associated with genTrapLastNumber allows easy detection of trap loss by the manager. For a given trap two different managers can receive it with a different value of genTrapPreviousNumber if they don't have subscribe to the same trap filters (see genManagerTable)."
          ::= { genTrapSpecificVariables 2 }


     --------------------------
     --  Objects under genTrapSpecificVarsTopology branch
     --------------------------

     genTrapSpecificVarsTopology OBJECT IDENTIFIER ::= { genTrapSpecificVariables 3 }

     genTrapTopoChangeType OBJECT-TYPE
          SYNTAX       INTEGER {
                                 genTrapObjectCreation(1),
                                 genTrapObjectDeletion(2),
                                 genTrapObjectChange(3)
                               }
          MAX-ACCESS   accessible-for-notify
          STATUS       current
          DESCRIPTION  "Enum that indicates more accuratly the topology change (ObjectCreation, ObjectDeletion, ObjectChange)"
          ::= { genTrapSpecificVarsTopology 1 }


     --------------------------
     --  Objects under genTrapSpecificVarsRedundancy branch
     --------------------------

     genTrapSpecificVarsRedundancy OBJECT IDENTIFIER ::= { genTrapSpecificVariables 4 }

     genTrapRedundancyStatusVar OBJECT-TYPE
          SYNTAX       INTEGER {
                                 standby(1),
                                 active(2),
                                 unsynchronized(5),
                                 maybeActive(6),
                                 maybeStandby(7)
                               }
          MAX-ACCESS   accessible-for-notify
          STATUS       current
          DESCRIPTION  "Enum that indicates the redundancy status (standby, active, unsynchronized, maybeActive, maybeStandby)"
          ::= { genTrapSpecificVarsRedundancy 1 }

     genTrapRedundancyGroupType OBJECT-TYPE
          SYNTAX       Unsigned32 
          MAX-ACCESS   accessible-for-notify
          STATUS       current
          DESCRIPTION  "Redundancy group concerned by the genTrapRedundancy trap"
          ::= { genTrapSpecificVarsRedundancy 2 }

     genTrapRedundancyGroupIndex OBJECT-TYPE
          SYNTAX       Unsigned32 
          MAX-ACCESS   accessible-for-notify
          STATUS       current
          DESCRIPTION  "Index of the group concerned by the genTrapRedundancy trap"
          ::= { genTrapSpecificVarsRedundancy 3 }

     genTrapRedundancyElementIndex OBJECT-TYPE
          SYNTAX       Unsigned32 
          MAX-ACCESS   accessible-for-notify
          STATUS       current
          DESCRIPTION  "Index of the element concerned by the genTrapRedundancy trap"
          ::= { genTrapSpecificVarsRedundancy 4 }

     genTrapRedundancyChangeType OBJECT-TYPE
          SYNTAX       INTEGER {
                                 genTrapObjectCreation(1),
                                 genTrapObjectDeletion(2),
                                 genTrapObjectChange(3)
                               }
          MAX-ACCESS   accessible-for-notify
          STATUS       current
          DESCRIPTION  "Enum that indicates more accuratly the redundancy change (ObjectCreation, ObjectDeletion, ObjectChange)"
          ::= { genTrapSpecificVarsRedundancy 5 }

     genTrapRedundancyElementName OBJECT-TYPE
          SYNTAX       DisplayString 
          MAX-ACCESS   accessible-for-notify
          STATUS       current
          DESCRIPTION  "Name of the element concerned by the genTrapRedundancyStatus trap"
          ::= { genTrapSpecificVarsRedundancy 6 }


     --------------------------
     --  Objects under genTrapSpecificVarsDecoder branch
     --------------------------

     genTrapSpecificVarsDecoder OBJECT IDENTIFIER ::= { genTrapSpecificVariables 5 }

     genTrapDecoderElementIndex OBJECT-TYPE
          SYNTAX       Unsigned32 
          MAX-ACCESS   accessible-for-notify
          STATUS       current
          DESCRIPTION  "Index of the element concerned by the genTrapConfigDecoder trap"
          ::= { genTrapSpecificVarsDecoder 1 }

     genTrapDecoderElementName OBJECT-TYPE
          SYNTAX       DisplayString 
          MAX-ACCESS   accessible-for-notify
          STATUS       current
          DESCRIPTION  "Name of the element concerned by the genTrapConfigDecoder trap"
          ::= { genTrapSpecificVarsDecoder 2 }


     --------------------------
     --  Objects under genTrapSpecificVarsEncoder branch
     --------------------------

     genTrapSpecificVarsEncoder OBJECT IDENTIFIER ::= { genTrapSpecificVariables 6 }

     genTrapEncoderInputElementIndex OBJECT-TYPE
          SYNTAX       Unsigned32 
          MAX-ACCESS   accessible-for-notify
          STATUS       current
          DESCRIPTION  "Index of the element concerned by the genTrapEncoderInput trap"
          ::= { genTrapSpecificVarsEncoder 1 }

     genTrapEncoderInputElementName OBJECT-TYPE
          SYNTAX       DisplayString 
          MAX-ACCESS   accessible-for-notify
          STATUS       current
          DESCRIPTION  "Name of the element concerned by the genTrapEncoderInput trap"
          ::= { genTrapSpecificVarsEncoder 2 }


     ----------------------
     --  TRAP DEFINITION
     ----------------------

     genTrapAlarm NOTIFICATION-TYPE
          OBJECTS      {
                         genTrapLastNumber,
                         genTrapPreviousNumber,
                         genEventRecordId,
                         genEventTime,
                         genEventOrigin,
                         genEventResourceId,
                         genEventProbableCause,
                         genEventSpecificProblem,
                         genEventSeverity,
                         genEventCategory,
                         genEventLabel
                       }
          STATUS       current
          DESCRIPTION  "TRAP associated to events of type alarm"
          ::= { genTraps 2 }


     ----------------------
     --  TRAP DEFINITION
     ----------------------

     genTrapTopology NOTIFICATION-TYPE
          OBJECTS      {
                         genTrapLastNumber,
                         genTrapPreviousNumber,
                         genTrapTopoChangeType,
                         topoElementIndex,
                         topoElementName,
                         topoElementType,
                         topoElementExtType,
                         topoElementParentIndex,
                         topoElementMaintenanceStatus,
                         topoElementIdleStatus,
                         topoElementOfflineStatus
                       }
          STATUS       current
          DESCRIPTION  "TRAP associated to topology change"
          ::= { genTraps 3 }


     ----------------------
     --  TRAP DEFINITION
     ----------------------

     genTrapConfigDecoder NOTIFICATION-TYPE
          OBJECTS      {
                         genTrapLastNumber,
                         genTrapPreviousNumber,
                         genTrapDecoderElementIndex,
                         genTrapDecoderElementName
                       }
          STATUS       current
          DESCRIPTION  "TRAP associated to configuration change"
          ::= { genTraps 4 }


     ----------------------
     --  TRAP DEFINITION
     ----------------------

     genTrapRedundancy NOTIFICATION-TYPE
          OBJECTS      {
                         genTrapLastNumber,
                         genTrapPreviousNumber,
                         genTrapRedundancyGroupIndex,
                         genTrapRedundancyGroupType,
                         genTrapRedundancyElementIndex,
                         genTrapRedundancyChangeType,
                         genTrapRedundancyElementName
                       }
          STATUS       current
          DESCRIPTION  "TRAP associated to redundancy change"
          ::= { genTraps 5 }


     ----------------------
     --  TRAP DEFINITION
     ----------------------

     genTrapRedundancyStatus NOTIFICATION-TYPE
          OBJECTS      {
                         genTrapLastNumber,
                         genTrapPreviousNumber,
                         genTrapRedundancyGroupIndex,
                         genTrapRedundancyElementIndex,
                         genTrapRedundancyStatusVar,
                         genTrapRedundancyElementName
                       }
          STATUS       current
          DESCRIPTION  "TRAP associated to redundancy status change"
          ::= { genTraps 6 }


     ----------------------
     --  TRAP DEFINITION
     ----------------------

     genTrapEncoderInput NOTIFICATION-TYPE
          OBJECTS      {
                         genTrapLastNumber,
                         genTrapPreviousNumber,
                         genTrapEncoderInputElementIndex,
                         genTrapEncoderInputElementName
                       }
          STATUS       current
          DESCRIPTION  "TRAP associated to SD encoders configuration change"
          ::= { genTraps 7 }


     ----------------------
     --  TRAP DEFINITION
     ----------------------

     genTrapEvent NOTIFICATION-TYPE
          OBJECTS      {
                         genTrapLastNumber,
                         genTrapPreviousNumber,
                         genEventRecordId,
                         genEventType,
                         genEventTime,
                         genEventOrigin,
                         genEventResourceId,
                         genEventLabel
                       }
          STATUS       current
          DESCRIPTION  "TRAP associated to events of other type than alarm"
          ::= { genTraps 8 }


     --------------------------
     --  Objects under topology branch
     --------------------------

     topology OBJECT IDENTIFIER ::= { xms3500 2 }


     -------
     -- topoElementTable definition
     -------

     topoElementTable OBJECT-TYPE
          SYNTAX       SEQUENCE OF TopoElementEntry
          MAX-ACCESS   not-accessible
          STATUS       current
          DESCRIPTION  ""
          ::= { topology 1 }

     topoElementEntry OBJECT-TYPE
          SYNTAX       TopoElementEntry
          MAX-ACCESS   not-accessible
          STATUS       current
          DESCRIPTION  ""
          INDEX        { topoElementIndex }
          ::= { topoElementTable 1 }

     TopoElementEntry ::=
          SEQUENCE {
                     topoElementIndex
                          Unsigned32,
                     topoElementName
                          DisplayString,
                     topoElementType
                          Unsigned32,
                     topoElementExtType
                          Unsigned32,
                     topoElementParentIndex
                          Unsigned32,
                     topoElementMaintenanceStatus
                          INTEGER,
                     topoElementIdleStatus
                          INTEGER,
                     topoElementOfflineStatus
                          INTEGER,
                     topoElementRid
                          DisplayString
                   }

     topoElementIndex OBJECT-TYPE
          SYNTAX       Unsigned32 
          MAX-ACCESS   read-only
          STATUS       current
          DESCRIPTION  "Index of a Network Element in the table"
          ::= { topoElementEntry 1 }

     topoElementName OBJECT-TYPE
          SYNTAX       DisplayString (SIZE(0..255))
          MAX-ACCESS   read-only
          STATUS       current
          DESCRIPTION  "Name of the Network Element"
          ::= { topoElementEntry 2 }

     topoElementType OBJECT-TYPE
          SYNTAX       Unsigned32 
          MAX-ACCESS   read-only
          STATUS       current
          DESCRIPTION  "Type of the Network Element"
          ::= { topoElementEntry 3 }

     topoElementExtType OBJECT-TYPE
          SYNTAX       Unsigned32 
          MAX-ACCESS   read-only
          STATUS       current
          DESCRIPTION  "Extended type of the Network Element"
          ::= { topoElementEntry 4 }

     topoElementParentIndex OBJECT-TYPE
          SYNTAX       Unsigned32 
          MAX-ACCESS   read-only
          STATUS       current
          DESCRIPTION  "Parent element index (typically an XMU. 0 means direct management by XMS)"
          ::= { topoElementEntry 5 }

     topoElementMaintenanceStatus OBJECT-TYPE
          SYNTAX       INTEGER {
                                 maintenanceModeOff(0),
                                 maintenanceModeOn(2)
                               }
          MAX-ACCESS   read-write
          STATUS       current
          DESCRIPTION  "Maintenance status of the Network Element"
          ::= { topoElementEntry 6 }

     topoElementIdleStatus OBJECT-TYPE
          SYNTAX       INTEGER {
                                 idleModeOff(0),
                                 idleModeOn(1),
                                 idleModeNoDownstreamAction(2)
                               }
          MAX-ACCESS   read-write
          STATUS       current
          DESCRIPTION  "Idle status of the Network Element"
          ::= { topoElementEntry 7 }

     topoElementOfflineStatus OBJECT-TYPE
          SYNTAX       INTEGER {
                                 offlineStatusOnline(0),
                                 offlineStatusOffline(2)
                               }
          MAX-ACCESS   read-write
          STATUS       current
          DESCRIPTION  "Offline status of a Mediation Unit"
          ::= { topoElementEntry 8 }

     topoElementRid OBJECT-TYPE
          SYNTAX       DisplayString 
          MAX-ACCESS   read-only
          STATUS       current
          DESCRIPTION  "Remote Inventory Data of the Network Element"
          ::= { topoElementEntry 9 }


     -------
     -- ipResourceTable definition
     -------

     ipResourceTable OBJECT-TYPE
          SYNTAX       SEQUENCE OF IpResourceEntry
          MAX-ACCESS   not-accessible
          STATUS       current
          DESCRIPTION  ""
          ::= { topology 2 }

     ipResourceEntry OBJECT-TYPE
          SYNTAX       IpResourceEntry
          MAX-ACCESS   not-accessible
          STATUS       current
          DESCRIPTION  ""
          INDEX        { ipResourceIndex }
          ::= { ipResourceTable 1 }

     IpResourceEntry ::=
          SEQUENCE {
                     ipResourceIndex
                          Unsigned32,
                     ipResourceElementIndex
                          Unsigned32,
                     ipResourceElementName
                          DisplayString,
                     ipResourceNetwork
                          DisplayString,
                     ipResourceType
                          DisplayString,
                     ipResourceLabel
                          DisplayString,
                     ipResourceAddress
                          IpAddress,
                     ipResourceDestinationPort
                          Unsigned32
                   }

     ipResourceIndex OBJECT-TYPE
          SYNTAX       Unsigned32 
          MAX-ACCESS   read-only
          STATUS       current
          DESCRIPTION  "Index of an IP resource in the table"
          ::= { ipResourceEntry 1 }

     ipResourceElementIndex OBJECT-TYPE
          SYNTAX       Unsigned32 
          MAX-ACCESS   read-only
          STATUS       current
          DESCRIPTION  "Reference to the Element containing the resource (value of the topoElementIndex field of the Element)"
          ::= { ipResourceEntry 2 }

     ipResourceElementName OBJECT-TYPE
          SYNTAX       DisplayString 
          MAX-ACCESS   read-only
          STATUS       current
          DESCRIPTION  "Name of the Element containing the resource (as defined in topoElementTable)"
          ::= { ipResourceEntry 3 }

     ipResourceNetwork OBJECT-TYPE
          SYNTAX       DisplayString 
          MAX-ACCESS   read-only
          STATUS       current
          DESCRIPTION  "Kind of network (control, data, media, CAS)"
          ::= { ipResourceEntry 4 }

     ipResourceType OBJECT-TYPE
          SYNTAX       DisplayString 
          MAX-ACCESS   read-only
          STATUS       current
          DESCRIPTION  "Type of the IP resource (Physical interface address, Virtual interface address, Stream source address, Multicast group(mcst))"
          ::= { ipResourceEntry 5 }

     ipResourceLabel OBJECT-TYPE
          SYNTAX       DisplayString 
          MAX-ACCESS   read-only
          STATUS       current
          DESCRIPTION  "Label of the IP resource (label of the physical port, (Stream) followed by stream name, (Flextream complexity), (Flextream allocated bitrate), or empty, depending on ipResourceType)"
          ::= { ipResourceEntry 6 }

     ipResourceAddress OBJECT-TYPE
          SYNTAX       IpAddress 
          MAX-ACCESS   read-only
          STATUS       current
          DESCRIPTION  "IP address"
          ::= { ipResourceEntry 7 }

     ipResourceDestinationPort OBJECT-TYPE
          SYNTAX       Unsigned32 
          MAX-ACCESS   read-only
          STATUS       current
          DESCRIPTION  "Destination port number of the IP resource (0 if not relevant)"
          ::= { ipResourceEntry 8 }


     --------------------------
     --  Objects under element branch
     --------------------------

     element OBJECT IDENTIFIER ::= { xms3500 3 }


     --------------------------
     --  Objects under decoder branch
     --------------------------

     decoder OBJECT IDENTIFIER ::= { element 1 }


     -------
     -- decoderTvChannelTable definition
     -------

     decoderTvChannelTable OBJECT-TYPE
          SYNTAX       SEQUENCE OF DecoderTvChannelEntry
          MAX-ACCESS   not-accessible
          STATUS       current
          DESCRIPTION  ""
          ::= { decoder 2 }

     decoderTvChannelEntry OBJECT-TYPE
          SYNTAX       DecoderTvChannelEntry
          MAX-ACCESS   not-accessible
          STATUS       current
          DESCRIPTION  ""
          INDEX        { decoderTvChannelElementIndex, decoderTvChannelChannelNbIndex }
          ::= { decoderTvChannelTable 1 }

     DecoderTvChannelEntry ::=
          SEQUENCE {
                     decoderTvChannelElementIndex
                          Unsigned32,
                     decoderTvChannelChannelNbIndex
                          Unsigned32,
                     decoderTvChannelPsi
                          INTEGER,
                     decoderTvChannelDecodedServiceId
                          Unsigned32
                   }

     decoderTvChannelElementIndex OBJECT-TYPE
          SYNTAX       Unsigned32 
          MAX-ACCESS   read-only
          STATUS       current
          DESCRIPTION  "Reference to the Element defining the decoder"
          ::= { decoderTvChannelEntry 1 }

     decoderTvChannelChannelNbIndex OBJECT-TYPE
          SYNTAX       Unsigned32 
          MAX-ACCESS   read-only
          STATUS       current
          DESCRIPTION  "Channel number reference"
          ::= { decoderTvChannelEntry 2 }

     decoderTvChannelPsi OBJECT-TYPE
          SYNTAX       INTEGER {
                                 off(1),
                                 on(2),
                                 atsc(3),
                                 iso(4)
                               }
          MAX-ACCESS   read-only
          STATUS       current
          DESCRIPTION  "Indicates use of PSI/SI information"
          ::= { decoderTvChannelEntry 3 }

     decoderTvChannelDecodedServiceId OBJECT-TYPE
          SYNTAX       Unsigned32 
          MAX-ACCESS   read-write
          STATUS       current
          DESCRIPTION  "Service Id to be used for decoding (configurable only if PSI is ON)"
          ::= { decoderTvChannelEntry 4 }


     --------------------------
     --  Objects under encoder branch
     --------------------------

     encoder OBJECT IDENTIFIER ::= { element 2 }


     -------
     -- encoderInputTable definition
     -------

     encoderInputTable OBJECT-TYPE
          SYNTAX       SEQUENCE OF EncoderInputEntry
          MAX-ACCESS   not-accessible
          STATUS       current
          DESCRIPTION  ""
          ::= { encoder 2 }

     encoderInputEntry OBJECT-TYPE
          SYNTAX       EncoderInputEntry
          MAX-ACCESS   not-accessible
          STATUS       current
          DESCRIPTION  ""
          INDEX        { encoderInputElementIndex, encoderInputIndex }
          ::= { encoderInputTable 1 }

     EncoderInputEntry ::=
          SEQUENCE {
                     encoderInputElementIndex
                          Unsigned32,
                     encoderInputIndex
                          Unsigned32,
                     encoderInputSource
                          INTEGER
                   }

     encoderInputElementIndex OBJECT-TYPE
          SYNTAX       Unsigned32 
          MAX-ACCESS   read-only
          STATUS       current
          DESCRIPTION  "Reference to the Element defining the encoder"
          ::= { encoderInputEntry 1 }

     encoderInputIndex OBJECT-TYPE
          SYNTAX       Unsigned32 
          MAX-ACCESS   read-only
          STATUS       current
          DESCRIPTION  "encoder input number reference (e.g. 1 to 4 for an EM1000)"
          ::= { encoderInputEntry 2 }

     encoderInputSource OBJECT-TYPE
          SYNTAX       INTEGER {
                                 sdi(1),
                                 analog(2),
                                 bar_pattern(3),
                                 black_pattern(4),
                                 custom_pattern1(5),
                                 custom_pattern2(6),
                                 custom_pattern3(7),
                                 custom_pattern4(8),
                                 ts_source(9)
                               }
          MAX-ACCESS   read-write
          STATUS       current
          DESCRIPTION  "Source to be used"
          ::= { encoderInputEntry 3 }


     --------------------------
     --  Objects under redundancy branch
     --------------------------

     redundancy OBJECT IDENTIFIER ::= { xms3500 4 }


     -------
     -- redGroupTable definition
     -------

     redGroupTable OBJECT-TYPE
          SYNTAX       SEQUENCE OF RedGroupEntry
          MAX-ACCESS   not-accessible
          STATUS       current
          DESCRIPTION  ""
          ::= { redundancy 1 }

     redGroupEntry OBJECT-TYPE
          SYNTAX       RedGroupEntry
          MAX-ACCESS   not-accessible
          STATUS       current
          DESCRIPTION  ""
          INDEX        { redGroupIndex }
          ::= { redGroupTable 1 }

     RedGroupEntry ::=
          SEQUENCE {
                     redGroupIndex
                          Unsigned32,
                     redGroupName
                          DisplayString,
                     redGroupType
                          INTEGER
                   }

     redGroupIndex OBJECT-TYPE
          SYNTAX       Unsigned32 
          MAX-ACCESS   read-only
          STATUS       current
          DESCRIPTION  "Index of a Redundancy Group in the table"
          ::= { redGroupEntry 1 }

     redGroupName OBJECT-TYPE
          SYNTAX       DisplayString (SIZE(0..255))
          MAX-ACCESS   read-only
          STATUS       current
          DESCRIPTION  "Name of the Redundancy Group"
          ::= { redGroupEntry 2 }

     redGroupType OBJECT-TYPE
          SYNTAX       INTEGER {
                                 fixed(1),
                                 switchableSource(2),
                                 floating(3),
                                 untiedTriggerGroup(4)
                               }
          MAX-ACCESS   read-only
          STATUS       current
          DESCRIPTION  "Type of the Redundancy Group (Fixed/Floating/SwitchableSource)"
          ::= { redGroupEntry 3 }


     --------------------------
     --  Objects under redReplaceableResource branch
     --------------------------

     redReplaceableResource OBJECT IDENTIFIER ::= { redundancy 2 }


     -------
     -- redResFixedTable definition
     -------

     redResFixedTable OBJECT-TYPE
          SYNTAX       SEQUENCE OF RedResFixedEntry
          MAX-ACCESS   not-accessible
          STATUS       current
          DESCRIPTION  ""
          ::= { redReplaceableResource 1 }

     redResFixedEntry OBJECT-TYPE
          SYNTAX       RedResFixedEntry
          MAX-ACCESS   not-accessible
          STATUS       current
          DESCRIPTION  ""
          INDEX        { redResFixedGroupIndex, redResFixedElementIndex }
          ::= { redResFixedTable 1 }

     RedResFixedEntry ::=
          SEQUENCE {
                     redResFixedGroupIndex
                          Unsigned32,
                     redResFixedElementIndex
                          Unsigned32,
                     redResFixedRedundancyStatus
                          INTEGER,
                     redResFixedFunction
                          INTEGER,
                     redResFixedSwitchMode
                          INTEGER,
                     redResFixedMirroredElementIndex
                          Unsigned32,
                     redResFixedBackupElementIndex
                          Unsigned32,
                     redResFixedSwitchCommand
                          INTEGER,
                     redResFixedRestoreMode
                          INTEGER
                   }

     redResFixedGroupIndex OBJECT-TYPE
          SYNTAX       Unsigned32 
          MAX-ACCESS   read-only
          STATUS       current
          DESCRIPTION  "Reference to the Redundancy Group handling the resource"
          ::= { redResFixedEntry 1 }

     redResFixedElementIndex OBJECT-TYPE
          SYNTAX       Unsigned32 
          MAX-ACCESS   read-only
          STATUS       current
          DESCRIPTION  "Reference to the Element defining the resource (value of the topoElementIndex field of the Element)"
          ::= { redResFixedEntry 2 }

     redResFixedRedundancyStatus OBJECT-TYPE
          SYNTAX       INTEGER {
                                 standby(1),
                                 active(2),
                                 maybeActive(6),
                                 maybeStandby(7)
                               }
          MAX-ACCESS   read-only
          STATUS       current
          DESCRIPTION  "Redundancy status of the resource (Active / Standby / maybeActive / maybeStandby)"
          ::= { redResFixedEntry 3 }

     redResFixedFunction OBJECT-TYPE
          SYNTAX       INTEGER {
                                 nominal(0),
                                 redundant(1)
                               }
          MAX-ACCESS   read-only
          STATUS       current
          DESCRIPTION  "Function of the resource (Nominal / Redundant)"
          ::= { redResFixedEntry 4 }

     redResFixedSwitchMode OBJECT-TYPE
          SYNTAX       INTEGER {
                                 manual(0),
                                 auto(1),
                                 switchBackOnRedundantFault(2),
                                 switchBackOnNominalFaultless(3),
                                 none(4),
                                 auto_controlled_by_xms(5),
                                 auto_controlled_by_switcher(6),
                                 auto_combined(7)
                               }
          MAX-ACCESS   read-only
          STATUS       current
          DESCRIPTION  "Switch mode (manual,auto backup, etc.). This field has a meaning only for nominal resources."
          ::= { redResFixedEntry 5 }

     redResFixedMirroredElementIndex OBJECT-TYPE
          SYNTAX       Unsigned32 
          MAX-ACCESS   read-write
          STATUS       current
          DESCRIPTION  "Reference to the resource (in this table) mirrored by this one. A reference to itself if this resource isn't mirroring any other one (this is the case for nominal resources)."
          ::= { redResFixedEntry 6 }

     redResFixedBackupElementIndex OBJECT-TYPE
          SYNTAX       Unsigned32 
          MAX-ACCESS   read-write
          STATUS       current
          DESCRIPTION  "Reference to the backup resource (in this table) selected to perform the switch command (by default the mirroring element, if any exists). Setting a '0' forces the XMS to choose itself the available redundant, in n+p schemes (but if none is available, the switch is not performed)."
          ::= { redResFixedEntry 7 }

     redResFixedSwitchCommand OBJECT-TYPE
          SYNTAX       INTEGER {
                                 switch(1),
                                 reactivate(2)
                               }
          MAX-ACCESS   read-write
          STATUS       current
          DESCRIPTION  "Switch/reactivate command. This command can be applied only on nominal resources."
          ::= { redResFixedEntry 8 }

     redResFixedRestoreMode OBJECT-TYPE
          SYNTAX       INTEGER {
                                 manual(1),
                                 switchBackOnNominalFaultless(2),
                                 switchBackOnRedundantFault(3),
                                 switchBackOnNominalOutputFaultless(4),
                                 switchBackOnRedundantOutputFault(5)
                               }
          MAX-ACCESS   read-only
          STATUS       current
          DESCRIPTION  "Restore mode. This field has a meaning only for nominal resources."
          ::= { redResFixedEntry 9 }


     -------
     -- redResFloatingTable definition
     -------

     redResFloatingTable OBJECT-TYPE
          SYNTAX       SEQUENCE OF RedResFloatingEntry
          MAX-ACCESS   not-accessible
          STATUS       current
          DESCRIPTION  ""
          ::= { redReplaceableResource 2 }

     redResFloatingEntry OBJECT-TYPE
          SYNTAX       RedResFloatingEntry
          MAX-ACCESS   not-accessible
          STATUS       current
          DESCRIPTION  ""
          INDEX        { redResFloatingGroupIndex, redResFloatingElementIndex }
          ::= { redResFloatingTable 1 }

     RedResFloatingEntry ::=
          SEQUENCE {
                     redResFloatingGroupIndex
                          Unsigned32,
                     redResFloatingElementIndex
                          Unsigned32,
                     redResFloatingRedundancyStatus
                          INTEGER,
                     redResFloatingFunction
                          INTEGER,
                     redResFloatingSwitchMode
                          INTEGER,
                     redResFloatingMirroredElementIndex
                          Unsigned32,
                     redResFloatingBackupElementIndex
                          Unsigned32,
                     redResFloatingSwitchCommand
                          INTEGER,
                     redResFloatingPriority
                          Unsigned32
                   }

     redResFloatingGroupIndex OBJECT-TYPE
          SYNTAX       Unsigned32 
          MAX-ACCESS   read-only
          STATUS       current
          DESCRIPTION  "Reference to the Redundancy Group handling the resource"
          ::= { redResFloatingEntry 1 }

     redResFloatingElementIndex OBJECT-TYPE
          SYNTAX       Unsigned32 
          MAX-ACCESS   read-only
          STATUS       current
          DESCRIPTION  "Reference to the Element defining the resource (value of the topoElementIndex field of the Element)"
          ::= { redResFloatingEntry 2 }

     redResFloatingRedundancyStatus OBJECT-TYPE
          SYNTAX       INTEGER {
                                 standby(1),
                                 active(2),
                                 unsynchronized(5),
                                 maybeActive(6),
                                 maybeStandby(7)
                               }
          MAX-ACCESS   read-only
          STATUS       current
          DESCRIPTION  "Redundancy status of the resource (Active / Standby / Unsynchronized / maybeActive / maybeStandby)"
          ::= { redResFloatingEntry 3 }

     redResFloatingFunction OBJECT-TYPE
          SYNTAX       INTEGER {
                                 initialActive(0),
                                 initialStandby(1)
                               }
          MAX-ACCESS   read-only
          STATUS       current
          DESCRIPTION  "Function of the resource (Initial active / Initial standby)"
          ::= { redResFloatingEntry 4 }

     redResFloatingSwitchMode OBJECT-TYPE
          SYNTAX       INTEGER {
                                 manual(0),
                                 auto(1),
                                 none(4)
                               }
          MAX-ACCESS   read-only
          STATUS       current
          DESCRIPTION  "Switch mode (manual, auto).  This field has a meaning only for active resources."
          ::= { redResFloatingEntry 5 }

     redResFloatingMirroredElementIndex OBJECT-TYPE
          SYNTAX       Unsigned32 
          MAX-ACCESS   read-write
          STATUS       current
          DESCRIPTION  "Reference to the resource (in this table) mirrored by this one. A reference to itself if this resource isn't mirroring any other one."
          ::= { redResFloatingEntry 6 }

     redResFloatingBackupElementIndex OBJECT-TYPE
          SYNTAX       Unsigned32 
          MAX-ACCESS   read-write
          STATUS       current
          DESCRIPTION  "Reference to the backup resource (in this table) selected to perform the switch command (by default the first mirroring element, if any exists)."
          ::= { redResFloatingEntry 7 }

     redResFloatingSwitchCommand OBJECT-TYPE
          SYNTAX       INTEGER { switch(1) }
          MAX-ACCESS   read-write
          STATUS       current
          DESCRIPTION  "Switch command.  This command can be applied only on active resources."
          ::= { redResFloatingEntry 8 }

     redResFloatingPriority OBJECT-TYPE
          SYNTAX       Unsigned32 
          MAX-ACCESS   read-only
          STATUS       current
          DESCRIPTION  "Priority of the resource (for floating redundancy management)"
          ::= { redResFloatingEntry 9 }


     -------
     -- redResSwitchableSourceTable definition
     -------

     redResSwitchableSourceTable OBJECT-TYPE
          SYNTAX       SEQUENCE OF RedResSwitchableSourceEntry
          MAX-ACCESS   not-accessible
          STATUS       current
          DESCRIPTION  ""
          ::= { redReplaceableResource 3 }

     redResSwitchableSourceEntry OBJECT-TYPE
          SYNTAX       RedResSwitchableSourceEntry
          MAX-ACCESS   not-accessible
          STATUS       current
          DESCRIPTION  ""
          INDEX        { redResSwitchSourceGroupIndex, redResSwitchSourceElementIndex }
          ::= { redResSwitchableSourceTable 1 }

     RedResSwitchableSourceEntry ::=
          SEQUENCE {
                     redResSwitchSourceGroupIndex
                          Unsigned32,
                     redResSwitchSourceElementIndex
                          Unsigned32,
                     redResSwitchSourceRedundancyStatus
                          INTEGER,
                     redResSwitchSourceFunction
                          INTEGER,
                     redResSwitchSourceSwitchMode
                          INTEGER,
                     redResSwitchSourceMirroredElementIndex
                          Unsigned32,
                     redResSwitchSourceBackupElementIndex
                          Unsigned32,
                     redResSwitchSourceSwitchCommand
                          INTEGER
                   }

     redResSwitchSourceGroupIndex OBJECT-TYPE
          SYNTAX       Unsigned32 
          MAX-ACCESS   read-only
          STATUS       current
          DESCRIPTION  "Reference to the Redundancy Group handling the source"
          ::= { redResSwitchableSourceEntry 1 }

     redResSwitchSourceElementIndex OBJECT-TYPE
          SYNTAX       Unsigned32 
          MAX-ACCESS   read-only
          STATUS       current
          DESCRIPTION  "Reference to the Element defining the source (value of the topoElementIndex field of the Element)"
          ::= { redResSwitchableSourceEntry 2 }

     redResSwitchSourceRedundancyStatus OBJECT-TYPE
          SYNTAX       INTEGER {
                                 standby(1),
                                 active(2),
                                 maybeActive(6),
                                 maybeStandby(7)
                               }
          MAX-ACCESS   read-only
          STATUS       current
          DESCRIPTION  "Redundancy status of the source (Active / Standby=replaced for a nominal source / maybeActive / maybeStandby)"
          ::= { redResSwitchableSourceEntry 3 }

     redResSwitchSourceFunction OBJECT-TYPE
          SYNTAX       INTEGER {
                                 nominal(0),
                                 buddy(1)
                               }
          MAX-ACCESS   read-only
          STATUS       current
          DESCRIPTION  "Function of the source in the group (Nominal / Buddy)"
          ::= { redResSwitchableSourceEntry 4 }

     redResSwitchSourceSwitchMode OBJECT-TYPE
          SYNTAX       INTEGER {
                                 manual(0),
                                 none(4)
                               }
          MAX-ACCESS   read-only
          STATUS       current
          DESCRIPTION  "Switch mode (always manual for a nominal resource and none for a buddy resource)"
          ::= { redResSwitchableSourceEntry 5 }

     redResSwitchSourceMirroredElementIndex OBJECT-TYPE
          SYNTAX       Unsigned32 
          MAX-ACCESS   read-only
          STATUS       current
          DESCRIPTION  "Reference to the nominal resource (in this table) mirrored by this one. A reference to itself if this resource is nominal."
          ::= { redResSwitchableSourceEntry 6 }

     redResSwitchSourceBackupElementIndex OBJECT-TYPE
          SYNTAX       Unsigned32 
          MAX-ACCESS   read-write
          STATUS       current
          DESCRIPTION  "Reference to the backup resource (in this table) selected to perform the switch command (by default the first buddy resource, if any exists)."
          ::= { redResSwitchableSourceEntry 7 }

     redResSwitchSourceSwitchCommand OBJECT-TYPE
          SYNTAX       INTEGER { switch(1) }
          MAX-ACCESS   read-write
          STATUS       current
          DESCRIPTION  "Switch command. This command can be applied only on the active resource."
          ::= { redResSwitchableSourceEntry 8 }

END
